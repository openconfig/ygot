// Copyright 2018 Google Inc.
//
// Licensed under the Apache License, Version 2.0 (the "License");
// you may not use this file except in compliance with the License.
// You may obtain a copy of the License at
//
//      http://www.apache.org/licenses/LICENSE-2.0
//
// Unless required by applicable law or agreed to in writing, software
// distributed under the License is distributed on an "AS IS" BASIS,
// WITHOUT WARRANTIES OR CONDITIONS OF ANY KIND, either express or implied.
// See the License for the specific language governing permissions and
// limitations under the License.
module getters-demo {
  prefix "urn:ygot:getters-demo";
  namespace "gd";

  container top {
    container config {
      uses top-config;
    }

    container state {
      config false;
      uses top-config;
    }

    container child {
      container config {
        uses child-config;
      }

      container state {
        config false;
        uses child-config;
      }
    }

    container child-lists {
      list child-list {
        key "k";

        leaf k {
          type leafref {
            path "../config/k";
          }
        }

        container config {
          uses child-config;
        }

        container state {
          config false;
          uses child-config;
        }
      }
    }
  }

  grouping top-config {
    leaf a {
      type string;
      default "A VALUE";
    }

    leaf b {
      type enumeration {
        enum A;
        enum B;
        enum C;
      }
      default C;
    }

    leaf c {
      type enumeration {
        enum ONE;
        enum TWO;
        enum THREE;
      }
    }

    leaf-list d {
      type string;
    }
  }

  grouping child-config {
    leaf k {
      type string;
    }

    leaf value-with-default {
      type uint32;
      default 42;
    }

    leaf value-without-default {
      type uint8;
    }
  }
}
