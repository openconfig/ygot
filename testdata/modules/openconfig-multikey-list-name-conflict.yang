module openconfig-multikey-list-name-conflict {
  namespace "urn:ocmklnc";
  prefix "oc";

  description
    "A simple test module that is used to verify name conflict resolution
    between a multi-key struct and a container for Go code generation";

  grouping multi-key-config {
    leaf key1 { type uint32; }
    leaf key2 { type uint64; }
  }

  grouping lists-top {
    container model {
      container a {
        list multi-key {
          key "key1 key2";

          leaf key1 {
            type leafref {
              path "../config/key1";
            }
          }

          leaf key2 {
            type leafref {
              path "../config/key2";
            }
          }

          container config {
            uses multi-key-config;
          }

          container state {
            config false;
            uses multi-key-config;
            // This container name is used to test name conflict resolution
            // with the multi-key struct for Go code generation.
            container key {
              leaf key3 { type uint8; }
            }
          }
        }
      }
    }
  }

  uses lists-top;

}
