module enum-types {
  prefix "t";
  namespace "urn:t";

  description
    "This module defines an identity to act as a common
     base across enum-types.";

  identity ID;

  typedef td {
    type union {
      type uint32;
      type enumeration {
        enum A;
        enum B;
        enum C;
      }
    }
  }

  typedef td2 {
    type union {
      type uint32;
      type enumeration {
        enum D;
        enum E;
        enum F;
      }
    }
  }

  typedef td-enum {
    type enumeration {
      enum ALPHA;
      enum BRAVO;
      enum CHARLIE;
    }
    default ALPHA;
  }

  typedef td-multi {
    type union {
      type uint32;
      type td;
      type enumeration {
        enum ONE;
        enum TWO;
        enum THREE;
      }
      // TODO(wenbli): td2's enum, td-enum, and the second enumeration are not being
      // generated because goyang fails to add them to the AST.
      type td2;
      type td-enum;
      type enumeration {
        enum FOUR;
        enum FIVE;
        enum SIX;
      }
    }
  }
}
