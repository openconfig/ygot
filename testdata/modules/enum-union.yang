module enum-union {
  prefix "eu";
  namespace "urn:eu";

  description
    "This module tests different types of enumerations within unions to make
    sure they're named correctly.";

  typedef weekend-days {
    type enumeration {
      enum SATURDAY;
      enum SUNDAY;
    }
  }

  typedef cyclone-scales {
    type union {
      type uint8;
      type enumeration {
        enum NORMAL;
        enum SUPER;
      }
    }
  }

  typedef days-of-week {
    type union {
      type uint8;
      type weekend-days;
    }
  }

  grouping union-enums {
    leaf leaf1 {
      type union {
        type uint64;
        type enumeration {
          enum ONE;
          enum TWO;
          enum THREE;
        }
      }
    }

    leaf leaf2 {
      type union {
        type uint64;
        type weekend-days;
      }
    }

    leaf leaf3 {
      type cyclone-scales;
    }

    leaf leaf4 {
      type days-of-week;
    }
  }

  container outer {
    container inner {
      container config {
        uses union-enums;
      }
      container state {
        config false;
        uses union-enums;
      }
    }
  }
}
