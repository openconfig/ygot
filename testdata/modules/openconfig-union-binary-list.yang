module openconfig-union-binary-list {
  namespace "urn:ocublist";
  prefix "oc";

  description
    "A simple test module that is used to verify code generation for a
    schema that contains a list with a union key containing a binary";

  grouping single-key-config {
    leaf key {
      type union {
        type string;
        type binary;
      }
    }
  }

  grouping lists-top {
    container model {
      container a {
        list single-key {
          key "key";

          leaf key {
            type leafref {
              path "../config/key";
            }
          }

          container config {
            uses single-key-config;
          }

          container state {
            config false;
            uses single-key-config;
          }
        }
      }
    }
  }

  uses lists-top;

}
