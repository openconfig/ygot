module openconfig-withlist {
  namespace "urn:ocwithlist";
  prefix "oc";

  description
    "A simple test module that is used to verify code generation for a
    schema that contains lists";

  grouping single-key-config {
    leaf key { type string; }
  }

  grouping multi-key-config {
    leaf key1 { type uint32; }
    leaf key2 { type uint64; }
  }

  grouping lists-top {
    container model {
      container a {
        list single-key {
          key "key";

          leaf key {
            type leafref {
              path "../config/key";
            }
          }

          container config {
            uses single-key-config;
          }

          container state {
            config false;
            uses single-key-config;
          }
        }
      }

      container b {
        list multi-key {
          key "key1

                key2"; // Test for irregular spacing

          leaf key1 {
            type leafref {
              path "../config/key1";
            }
          }

          leaf key2 {
            type leafref {
              path "../config/key2";
            }
          }

          container config {
            uses multi-key-config;
          }

          container state {
            config false;
            uses multi-key-config;
          }
        }
      }

      container c {
        list single-key-ordered {
          key "key";
          ordered-by user;

          leaf key {
            type leafref {
              path "../config/key";
            }
          }

          container config {
            uses single-key-config;
          }

          container state {
            config false;
            uses single-key-config;
          }
        }
      }
    }
  }

  uses lists-top;

}
