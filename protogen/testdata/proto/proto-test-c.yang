module proto-test-c {
  yang-version 1.1;
  prefix "proto-c";
  namespace "urn:proto-c";

  typedef enum-with-default {
    type enumeration {
      enum A;
      enum B;
    }
    default "B";
  }

  grouping entity-cfg {
    leaf enumerated-leaf {
      type enumeration {
        enum UP;
        enum DOWN;
      }
    }

    leaf enumerated-with-default {
      type enumeration {
        enum A;
        enum B;
      }
      default "A";
    }

    leaf-list enumerated-with-default-list-single-default-at-type {
      type enum-with-default;
    }

    leaf-list enumerated-with-default-list-single-default {
      type enumeration {
        enum A;
        enum B;
      }
      default "B";
    }

    leaf-list enumerated-with-default-list-multiple-default {
      type enumeration {
        enum A;
        enum B;
      }
      default "A";
      default "B";
    }
  }

  container entity {
    container config {
      uses entity-cfg;
    }
    container state {
      config false;
      uses entity-cfg;
    }
  }

  grouping elist-cfg {
    leaf one {
      type enumeration {
        enum E0;
        enum E1;
        enum E42 {
          value 42;
        }
      }
    }

    leaf two {
      type string;
    }

    leaf three {
      type enum-with-default;
    }

    leaf non-key {
      type string;
    }
  }

  container elists {
    list elist {
      key "one two three";

      leaf one {
        type leafref {
          path "../config/one";
        }
      }

      leaf two {
        type leafref {
          path "../config/two";
        }
      }

      leaf three {
        type leafref {
          path "../config/three";
        }
      }

      container config {
        uses elist-cfg;
      }

      container state {
        config false;
        uses elist-cfg;
      }
    }
  }
}
