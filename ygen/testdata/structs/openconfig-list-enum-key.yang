module openconfig-list-enum-key {
  prefix "oc";
  namespace "urn:oclek";

  identity foo-identity;

  identity BAR {
    base "foo-identity";
  }

  identity BAZ {
    base "foo-identity";
  }

  grouping sk-config {
    leaf k {
      type enumeration {
        enum A;
        enum B;
      }
    }
  }

  grouping mk-config {
    leaf k1 {
      type enumeration {
        enum A;
        enum B;
      }
    }

    leaf k2 {
      type identityref {
        base "foo-identity";
      }
    }
  }

  grouping foo-top {
    container top {
      container single-key {
        list eks {
          key "k";

          leaf k {
            type leafref {
              path "../config/k";
            }
          }

          container config {
            uses sk-config;
          }

          container state {
            config false;
            uses sk-config;
          }
        }
      }

      container multi-key {
        list ekm {
          key "k1 k2";

          leaf k1 {
            type leafref {
              path "../config/k1";
            }
          }

          leaf k2 {
            type leafref {
              path "../config/k2";
            }
          }

          container config {
            uses mk-config;
          }

          container state {
            config false;
            uses mk-config;
          }
        }
      }
    }
  }

  uses foo-top;
}
