module proto-test-a {
  prefix "proto-a";
  namespace "urn:proto-a";

  description
    "Test YANG simple scheam for protobuf
    translation.";

  import openconfig-codegen-extensions { prefix occodegenext; }

  grouping child-cfg {
    leaf string { type string; }
    leaf integer { type int64; }
    leaf uinteger { type uint64; }
    leaf leaf-with-dashes { type string; }
    leaf-list leaf-list { type string; }

    leaf uleaf {
      type union {
        type string;
        type uint32;
      }
    }
  }

  grouping child-state {
    leaf boolean {
      type boolean;
      occodegenext:field-number 1;
      occodegenext:field-number-offset 100;
    }
  }

  container parent {
    container child {
      container config {
        uses child-cfg;
      }

      container state {
        config false;
        uses child-cfg;
        uses child-state {
          occodegenext:field-number-offset 100;
        }
      }
    }
  }
}
