module refschema {
  prefix "rs";
  namespace "urn:rs";

  import utestschema { prefix "ts"; }

  container ref {
    list reference {
      key "name";

      leaf name { 
        type leafref {
          path "/ts:target/ts:entity/ts:name";
        }
      }
    } 
  }
}
